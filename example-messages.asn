message Message ::= {
  version 1,
  caller "aaaaa",
  callee "bbbbb",
  payload format-request 774
}

message Message ::= {
  version 1,
  caller "aaaaa",
  callee "bbbbb",
  payload format-response: {
    rid             774,
    assessment-id   { 1 1 1 },
    assessment-def  "Formats DEFINITIONS ::=
                     BEGIN
                       QTM ::= ENUMERATED {
                         very-bad (0),
                         bad (1),
                         neutral (2),
                         good (3),
                         very-good (4)
                       }
                     END",
    trust-id        { 1 1 1 },
    trust-def       "Formats DEFINITIONS ::=
                     BEGIN
                      QTM ::= ENUMERATED {
                        very-bad (0),
                        bad (1),
                        neutral (2),
                        good (3),
                        very-good (4)
                      }
                    END"
  }
}

message Message ::= {
  version 1,
  caller "aaaaa",
  callee "bbbbb",
  payload data-request: {
    rid 113,
    type assessment,
    query con: {
      operator ge,
      value date: 1499356643
    }
  }
}

message Message ::= {
  version 1,
  caller "aaaaa",
  callee "bbbbb",
  payload data-request: {
    rid 113,
    type assessment,
    query exp: {
      operator and,
      left con: {
        operator ge,
        value date: 1499356643
      },
      right con: {
        operator eq,
        value target: "bob"
      }
    }
  }
}

message Message ::= {
  version 1,
  caller "aaaaa",
  callee "bbbbb",
  payload data-response: {
    rid 113,
    format { 1 1 1 },
    type assessment,
    response {
      {
        source "alice",
        target "bob",
        service "seller",
        date 10,
        value '0a0103'H
      },
      {
        source "charlie",
        target "bob",
        service "seller",
        date 20,
        value '0a0104'H
      }
    }
  }
}

message Message ::= {
  version 1,
  caller "aaaaa",
  callee "bbbbb",
  payload fault: {
    rid 10,
    message "Internal error. Try again later."
  }
}


message Message ::= {
  version 1,
  caller "aaaaa",
  callee "bbbbb",
  payload data-request {
    rid 591,
    type assessment,
    query exp: {
      operator and,
      left exp: {
        operator and,
        left con: {
          operator eq,
          value target: "bob"
        },
        right exp: {
          operator or,
          left con: {
            operator eq,
            value service: "seller"
          },
          right con: {
            operator eq,
            value service: "buyer"
          }
        }
      },
      right con: {
        operator gt,
        value date: 20
      }
    }
  }
}
