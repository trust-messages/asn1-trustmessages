Messages DEFINITIONS ::= BEGIN

Message ::= SEQUENCE {
  version INTEGER,
  caller  Entity,
  callee  Entity,
  payload CHOICE {
    data-request      DataRequest,
    data-response     DataResponse,
    format-request    FormatRequest,
    format-response   FormatResponse,
    fault             Fault
  }
}

FormatRequest ::= [APPLICATION 0] IMPLICIT INTEGER

FormatResponse ::= [APPLICATION 1] IMPLICIT SEQUENCE {
  rid             INTEGER,
  assessment-id   Format,
  assessment-def  IA5String,
  trust-id        Format,
  trust-def       IA5String
}

DataRequest ::= [APPLICATION 2] IMPLICIT SEQUENCE {
  rid   INTEGER,
  type  Type,
  query Query
}

DataResponse ::= [APPLICATION 3] IMPLICIT SEQUENCE {
  rid       INTEGER,
  format    Format,
  type      Type,
  response  SEQUENCE OF Rating
}

Rating ::= [APPLICATION 4] IMPLICIT SEQUENCE {
  source  Entity,
  target  Entity,
  service Service,
  date    BinaryTime,
  value   OCTET STRING
-- ANY
}

Query ::= CHOICE {
  con Constraint,
  exp Expression
}

Constraint ::= [APPLICATION 5] IMPLICIT SEQUENCE {
    operator  ENUMERATED {
      eq (0), ne (1), lt (2),
      le (3), gt (4), ge (5)
    },
    value     Value
}

Expression ::= [APPLICATION 6] IMPLICIT SEQUENCE {
  operator  ENUMERATED { and (0), or (1) },
  left      Query,
  right     Query
}

Value ::= CHOICE {
  source  [APPLICATION 0] IMPLICIT Entity,
  target  [APPLICATION 1] IMPLICIT Entity,
  date    [APPLICATION 2] IMPLICIT BinaryTime,
  service [APPLICATION 3] IMPLICIT Service
}

Fault ::= [APPLICATION 7] IMPLICIT SEQUENCE {
  rid     INTEGER,
  message IA5String
}

DataSubscription ::= [APPLICATION 8] IMPLICIT SEQUENCE {
  type  Type OPTIONAL,
  query Query OPTIONAL
}

DataCancellation ::= [APPLICATION 9] IMPLICIT SEQUENCE {
  type  Type OPTIONAL,
  query Query OPTIONAL
}

DataUpdate ::= [APPLICATION 10] IMPLICIT SEQUENCE {
  format  Format,
  type    Type,
  rating  Rating
}

Type ::=  ENUMERATED {
  trust (0),
  assessment (1)
}

Format ::= OBJECT IDENTIFIER

Entity ::= IA5String

Service ::= IA5String

BinaryTime ::= INTEGER

END
